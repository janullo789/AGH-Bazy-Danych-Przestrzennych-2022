FME workspace Cw10.fmw

Parameters:
- SourceDataset_SHAPEFILE = ""$(FME_MF_DIR)Dane - Ćwiczenia 8\T2019_KAR_GERMANY\T2019_KAR_STREETS.shp" "$(FME_MF_DIR)Dane - Ćwiczenia 8\T2019_KAR_GERMANY\T2019_KAR_POI_TABLE.shp" "$(FME_MF_DIR)Dane - Ćwiczenia 8\T2019_KAR_GERMANY\T2019_KAR_STREET_NODE.shp""   # Source Esri Shapefile(s)
- SourceDataset_CSV2 = $(FME_MF_DIR)Dane - Ćwiczenia 8\routePoints.csv   # Source CSV (Comma Separated Value) File(s)
- DestDataset_GEOJSON_5 = $(FME_MF_DIR)plikZ6.json   # Destination GeoJSON File
- DestDataset_GEOJSON = $(FME_MF_DIR)plikZ6.json   # Destination GeoJSON File

Readers:
- SHAPEFILE_1: SHAPEFILE from $(SourceDataset_SHAPEFILE) in LL-WGS84
- CSV2_1: CSV2 from $(SourceDataset_CSV2) in LL-WGS84

Writers:
- GEOJSON_1: GEOJSON to $(DestDataset_GEOJSON)
- GEOJSON_2: GEOJSON to $(DestDataset_GEOJSON_5) in DHDN.Berlin/Cassini

Bookmark: Zad 1
T2019_KAR_POI_TABLE (reader SHAPEFILE_1)
    attributes: POI_ID long, LINK_ID long, TYPE varchar(250), POI_NAME varchar(250), ST_NAME varchar(250), LAT number(31,15), LON number(31,15)
    -> T2019_KAR_POI_TABLE
    -> Reprojector
T2019_KAR_POI_TABLE: Inspector
T2019_KAR_STREET_NODE (reader SHAPEFILE_1)
    attributes: NODE_ID long, LINK_ID long, POINT_NUM long, Z_LEVEL long, INTERSECT varchar(1), LAT number(31,15), LON number(31,15)
    -> T2019_KAR_STREET_NODE
    -> Reprojector_2
T2019_KAR_STREET_NODE: Inspector
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> T2019_KAR_STREETS
    -> Reprojector_3
T2019_KAR_STREETS: Inspector

Bookmark: Zad 4
Reprojector
    DEST = DHDN.Berlin/Cassini
    INTERPOLATION_TYPE_NAME = Nearest Neighbor
    RASTER_CELL_SIZE = Preserve Cells
    RASTER_TOLERANCE = 0.0
    SOURCE = LL-WGS84
    REPROJECTED -> SpatialFilter [Candidate]
    REPROJECTED -> SpatialFilter_2 [Candidate]
Reprojector_2
    DEST = DHDN.Berlin/Cassini
    INTERPOLATION_TYPE_NAME = Nearest Neighbor
    RASTER_CELL_SIZE = Preserve Cells
    RASTER_TOLERANCE = 0.0
    SOURCE = LL-WGS84
    REPROJECTED -> PointOnLineOverlayer [POINT]
    REPROJECTED -> PointOnLineOverlayer_2 [POINT]
Reprojector_3
    DEST = DHDN.Berlin/Cassini
    INTERPOLATION_TYPE_NAME = Nearest Neighbor
    RASTER_CELL_SIZE = Preserve Cells
    RASTER_TOLERANCE = 0.0
    SOURCE = LL-WGS84
    REPROJECTED -> ShortestPathFinder [NETWORK]
    REPROJECTED -> Tester
Reprojector_4
    DEST = DHDN.Berlin/Cassini
    INTERPOLATION_TYPE_NAME = Nearest Neighbor
    RASTER_CELL_SIZE = Preserve Cells
    RASTER_TOLERANCE = 0.0
    SOURCE = LL-WGS84
    REPROJECTED -> ShortestPathFinder [FROM-TO]
    REPROJECTED -> ShortestPathFinder_2 [FROM-TO]

Bookmark: Zad 5b
Tester
    BOOL_OP = OR
    TEST_CLAUSE:
      TEST @Value(DIR_TRAVEL) = T
      TEST @Value(DIR_TRAVEL) = B
    TEST_MODE = TEST
    PASSED -> AttributeManager
    FAILED -> AttributeManager_2
AttributeManager
    ATTR_TABLE:
      SET_TO ForwardCost = 1
      SET_TO ReverseCost = 9999
    -> ShortestPathFinder_2 [NETWORK]
AttributeManager_2
    ATTR_TABLE:
      SET_TO ForwardCost = 1
      SET_TO ReverseCost = 1
    -> ShortestPathFinder_2 [NETWORK]
ShortestPathFinder_2
    ALLOW_UTURNS = Yes
    REORDER_MODE = NONE
    SNAP_POINTS = No
    WEIGHT_ATTR_1 = ForwardCost
    WEIGHT_ATTR_2 = ReverseCost
    WEIGHT_ATTR_CHOICE = BY_TWO_ATTRIBUTES
    PATH -> ShortestPathFinder_2_Path
    PATH -> Bufferer_2
    PATH -> PointOnLineOverlayer_2 [LINE]
ShortestPathFinder_2_Path: Inspector

Bookmark: Zad 2
CSV (reader CSV2_1)
    attributes: x x_coordinate, y y_coordinate
    -> CSV
    -> LineBuilder
CSV: Inspector

Bookmark: Zad 3
LineBuilder
    ACCUM_INPUT_ATTRS = Use Attributes From One Feature
    REMOVE_DUPLICATES = No
    LINE -> Reprojector_4

Bookmark: Zad 5a
ShortestPathFinder
    ALLOW_UTURNS = Yes
    REORDER_MODE = NONE
    SNAP_POINTS = Yes
    SNAP_TOLERANCE = 200
    WEIGHT_ATTR_CHOICE = BY_LENGTH
    PATH -> ShortestPathFinder_Path
    PATH -> Bufferer
    PATH -> PointOnLineOverlayer [LINE]
ShortestPathFinder_Path: Inspector

Bookmark: Zadanie 7 (bez kosztów)
PointOnLineOverlayer
    DEAGGREGATE_INPUT = Yes
    MEASURE_TYPE = Continuous
    MERGE_MEASURES = Yes
    OV_ATTR = _overlaps
    TOLERANCE = 0
    POINT -> Tester_2
Tester_2
    BOOL_OP = OR
    TEST_CLAUSE = TEST @Value(_overlaps) = 1
    TEST_MODE = TEST
    PASSED -> PointOnLineOverlayer_Point
PointOnLineOverlayer_Point: Inspector

Bookmark: Zad 6
Bufferer
    ANGLE = 22.5
    CAP_STYLE = Arc
    CORNER_STYLE = Arc
    MODE = AREA
    OFFSET = 5
    OFFSET_UNITS = METERS
    PRECISION = APPROX
    BUFFERED -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialFilter_Passed
    PASSED -> T2019_KAR_POI_TABLE (writer GEOJSON_2)
SpatialFilter_Passed: Inspector
Bufferer_2
    ANGLE = 22.5
    CAP_STYLE = Arc
    CORNER_STYLE = Arc
    MODE = AREA
    OFFSET = 5
    OFFSET_UNITS = METERS
    PRECISION = APPROX
    BUFFERED -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> T2019_KAR_POI_TABLE (writer GEOJSON_2)
    PASSED -> SpatialFilter_2_Passed
T2019_KAR_POI_TABLE (writer GEOJSON_2)
    attributes: POI_ID int, LINK_ID int, TYPE string, POI_NAME string, ST_NAME string, LAT float, LON float
SpatialFilter_2_Passed: Inspector

Bookmark: Zadanie 7 (z kosztami)
PointOnLineOverlayer_2
    DEAGGREGATE_INPUT = Yes
    MEASURE_TYPE = Continuous
    MERGE_MEASURES = Yes
    OV_ATTR = _overlaps
    TOLERANCE = 0
    POINT -> Tester_3
Tester_3
    BOOL_OP = OR
    TEST_CLAUSE = TEST @Value(_overlaps) = 1
    TEST_MODE = TEST
    PASSED -> PointOnLineOverlayer_Point_2
PointOnLineOverlayer_Point_2: Inspector
